import FreeCAD as App
import FreeCADGui as Gui
import Part

# Handle PySide imports gracefully for different FreeCAD versions
try:
    from PySide6 import QtWidgets, QtCore
except ImportError:
    from PySide2 import QtWidgets, QtCore

class TwistHandleDialog(QtWidgets.QDialog):
    def __init__(self):
        super().__init__()
        self.setWindowTitle("Twisted Handle Generator")
        self.resize(350, 400)
        
        # Main layout
        layout = QtWidgets.QVBoxLayout(self)
        
        # Instructions
        label = QtWidgets.QLabel("1. Select a Sketch in the tree view.\n2. Add your Z-Height and Twist data below.\n3. Click Generate.")
        layout.addWidget(label)
        
        # Table for our data
        self.table = QtWidgets.QTableWidget(0, 2)
        self.table.setHorizontalHeaderLabels(["Z Height (mm)", "Twist (Degrees)"])
        # Make the columns stretch to fit the window
        self.table.horizontalHeader().setSectionResizeMode(QtWidgets.QHeaderView.Stretch)
        layout.addWidget(self.table)
        
        # Pre-fill with default data so you don't start empty
        default_data = [(0, 0), (20, 15), (50, 45), (90, 90), (110, 100), (120, 100)]
        for z, angle in default_data:
            self.add_row(str(z), str(angle))
            
        # Add/Remove Buttons Layout
        btn_layout = QtWidgets.QHBoxLayout()
        
        self.btn_add = QtWidgets.QPushButton("+ Add Row")
        self.btn_add.clicked.connect(lambda: self.add_row("0", "0"))
        btn_layout.addWidget(self.btn_add)
        
        self.btn_rem = QtWidgets.QPushButton("- Remove Row")
        self.btn_rem.clicked.connect(self.remove_row)
        btn_layout.addWidget(self.btn_rem)
        
        layout.addLayout(btn_layout)
        
        # Generate Button
        self.btn_gen = QtWidgets.QPushButton("Generate Handle")
        self.btn_gen.clicked.connect(self.generate)
        # Give it a nice bold look
        self.btn_gen.setStyleSheet("font-weight: bold; padding: 10px;")
        layout.addWidget(self.btn_gen)

    def add_row(self, z_val, angle_val):
        row_idx = self.table.rowCount()
        self.table.insertRow(row_idx)
        self.table.setItem(row_idx, 0, QtWidgets.QTableWidgetItem(z_val))
        self.table.setItem(row_idx, 1, QtWidgets.QTableWidgetItem(angle_val))

    def remove_row(self):
        # Removes the currently selected row
        current_row = self.table.currentRow()
        if current_row >= 0:
            self.table.removeRow(current_row)

    def generate(self):
        # 1. Grab current selection at the moment the button is clicked
        selection = Gui.Selection.getSelection()
        if not selection:
            App.Console.PrintError("UI Error: Please select a Sketch first!\n")
            return

        base_obj = selection[0]
        if not hasattr(base_obj, "Shape") or base_obj.Shape.isNull():
            App.Console.PrintError("UI Error: Selected object has no shape.\n")
            return

        # 2. Extract data from the table
        sections_data = []
        for row in range(self.table.rowCount()):
            try:
                z = float(self.table.item(row, 0).text())
                angle = float(self.table.item(row, 1).text())
                sections_data.append((z, angle))
            except ValueError:
                App.Console.PrintError(f"UI Error: Invalid number in row {row + 1}.\n")
                return

        # 3. Generate the 3D Loft
        doc = App.ActiveDocument
        profiles = []
        
        for z, angle in sections_data:
            profile_copy = base_obj.Shape.copy()
            profile_copy.translate(App.Vector(0, 0, z))
            profile_copy.rotate(App.Vector(0, 0, z), App.Vector(0, 0, 1), angle)
            
            if profile_copy.Wires:
                profiles.append(profile_copy.Wires[0])
            else:
                App.Console.PrintError("UI Error: Could not extract wireframe.\n")
                return

        handle_loft = Part.makeLoft(profiles, True, False)
        
        new_obj_name = "Twisted_" + base_obj.Name
        obj = doc.addObject("Part::Feature", new_obj_name)
        obj.Shape = handle_loft
        
        doc.recompute()
        App.Console.PrintMessage("Handle generated successfully from UI!\n")
        
        # Optional: Close the window after generating
        # self.accept() 

# Run the UI
dialog = TwistHandleDialog()
dialog.show()
