import FreeCAD as App
import FreeCADGui as Gui
import Part
import os

from SharedLib.UI import BaseTaskPanel

class SkeletonTaskPanel(BaseTaskPanel):
    def __init__(self):
        macro_dir = os.path.dirname(os.path.abspath(__file__))
        ui_path = os.path.join(macro_dir, "ui", "skeleton_panel.ui")

        super().__init__(ui_path)

    def setup_ui(self):
        """Link the Qt Designer UI widgets to the debouncer."""
        self.form.param_spin.valueChanged.connect(self.queue_preview) # Auto mapped from .ui file

    def calculate_preview(self):
        """Fast, lightweight math for live preview."""
        size = max(1.0, self.form.param_spin.value())
        return Part.makeBox(size, size, size)

    def generate_final(self):
        """Heavy generation when OK is clicked."""
        doc = App.ActiveDocument
        size = self.form.param_spin.value()

        new_obj = doc.addObject("Part::Box", "FinalObject")
        new_obj.Length = size
        new_obj.Width = size
        new_obj.Height = size
        doc.recompute()

if not App.ActiveDocument:
    App.Console.PrintError("Error: You must have an active document open.\n")
else:
    if Gui.Control.activeDialog():
        Gui.Control.closeDialog()

    panel = SkeletonTaskPanel()
    Gui.Control.showDialog(panel)
