import FreeCAD as App
import FreeCADGui as Gui
import Part
import math
from PySide6 import QtWidgets
import importlib

from SharedLib import MacroShared
importlib.reload(MacroShared)

# ==========================================
# CORE LOGIC
# ==========================================

def calculate_hex_shape(target_obj, tile_radius=5.0, gap=0.5, mode="cut", offset_x=0.0, offset_y=0.0, strict_mode=False):
    """
    Calculates and returns the resulting Shape of a hex pattern applied to target_obj.
    No document side-effects occur here.
    """
    bbox = target_obj.Shape.BoundBox
    step_radius = tile_radius + gap

    # Grid math
    dx = 1.5 * step_radius
    dy = math.sqrt(3) * step_radius

    # Calculate how many columns/rows are needed to cover the BBox
    cols = int((bbox.XMax - bbox.XMin) / dx) + 2
    rows = int((bbox.YMax - bbox.YMin) / dy) + 2

    hex_faces = []

    z_min_line = bbox.ZMin - 10
    z_max_line = bbox.ZMax + 10
    target_shape = target_obj.Shape

    # Helper for Strict Mode: Checks if a vertical line through (px, py) hits the object
    def is_point_inside(px, py):
        line = Part.makeLine(App.Vector(px, py, z_min_line), App.Vector(px, py, z_max_line))
        # distToShape returns a tuple where the first element is the shortest distance
        return line.distToShape(target_shape)[0] <= 1e-4

    # Generate the 2D grid
    for c in range(-3, cols + 3):
        for r in range(-3, rows + 3):
            # Apply offsets to base coordinates
            x = bbox.XMin + c * dx + offset_x
            y = bbox.YMin + r * dy + offset_y

            # Offset every odd column
            if c % 2 != 0:
                y += dy / 2.0

            # Calculate the 6 vertices of the hexagon
            pts = []
            for i in range(6):
                angle_deg = i * 60
                angle_rad = math.radians(angle_deg)
                pts.append(App.Vector(
                    x + tile_radius * math.cos(angle_rad),
                    y + tile_radius * math.sin(angle_rad),
                    bbox.ZMin - 10 # Start slightly below the object bounds
                ))

            # --- STRICT MODE FILTERING ---
            if strict_mode:
                # Fast fail: check center first
                if not is_point_inside(x, y):
                    continue

                # Check all 6 outer vertices
                valid_hex = True
                for pt in pts:
                    if not is_point_inside(pt.x, pt.y):
                        valid_hex = False
                        break

                if not valid_hex:
                    continue
            # -----------------------------

            pts.append(pts[0]) # Close the loop
            polygon = Part.makePolygon(pts)
            hex_faces.append(Part.Face(polygon))

    # Fail-safe: if strict mode culled EVERY hexagon (e.g. radius is too big)
    if not hex_faces:
        if mode == "cut":
            return target_obj.Shape.copy() # No cuts made
        else:
            return Part.makeCompound([])   # Nothing to keep

    # Fuse and Extrude the grid into 3D pillars
    grid_compound = Part.makeCompound(hex_faces)
    z_height = (bbox.ZMax - bbox.ZMin) + 20
    hex_pillars = grid_compound.extrude(App.Vector(0, 0, z_height))

    # Perform the selected Boolean Operation
    if mode == "cut":
        return target_obj.Shape.cut(hex_pillars)
    else:
        return target_obj.Shape.common(hex_pillars)


# ==========================================
# GUI LOGIC (Native Task Panel)
# ==========================================

class SmartHexTaskPanel:
    def __init__(self, target_obj):
        self.target_obj = target_obj
        self.form = QtWidgets.QWidget()
        layout = QtWidgets.QVBoxLayout(self.form)

        instruction_text = (
            "<b>1.</b> Adjust hex sizes, gap, and offsets.<br>"
            "<b>2.</b> View live preview in the 3D window.<br>"
            "<b>3.</b> Click OK to apply or Cancel to revert."
        )
        layout.addWidget(QtWidgets.QLabel(instruction_text))

        form_layout = QtWidgets.QFormLayout()

        # Tile Radius
        self.radius_spin = QtWidgets.QDoubleSpinBox()
        self.radius_spin.setRange(0.1, 1000.0)
        self.radius_spin.setValue(8.0)
        self.radius_spin.setSuffix(" mm")
        self.radius_spin.setToolTip("The radius of a single hexagon tile.")
        self.radius_spin.setKeyboardTracking(False)
        form_layout.addRow("Tile Radius:", self.radius_spin)

        # Gap Size
        self.gap_spin = QtWidgets.QDoubleSpinBox()
        self.gap_spin.setRange(0.0, 500.0)
        self.gap_spin.setValue(1.0)
        self.gap_spin.setSuffix(" mm")
        self.gap_spin.setToolTip("The space between tiles (creates the lattice walls).")
        self.gap_spin.setKeyboardTracking(False)
        form_layout.addRow("Gap Size:", self.gap_spin)

        # X Offset
        self.offset_x_spin = QtWidgets.QDoubleSpinBox()
        self.offset_x_spin.setRange(-1000.0, 1000.0)
        self.offset_x_spin.setValue(0.0)
        self.offset_x_spin.setSuffix(" mm")
        self.offset_x_spin.setToolTip("Shift the entire pattern along the X axis.")
        self.offset_x_spin.setKeyboardTracking(False)
        form_layout.addRow("X Offset:", self.offset_x_spin)

        # Y Offset
        self.offset_y_spin = QtWidgets.QDoubleSpinBox()
        self.offset_y_spin.setRange(-1000.0, 1000.0)
        self.offset_y_spin.setValue(0.0)
        self.offset_y_spin.setSuffix(" mm")
        self.offset_y_spin.setToolTip("Shift the entire pattern along the Y axis.")
        self.offset_y_spin.setKeyboardTracking(False)
        form_layout.addRow("Y Offset:", self.offset_y_spin)

        # Operation Toggle
        self.operation_combo = QtWidgets.QComboBox()
        self.operation_combo.addItem("Cut (Create Lattice)")
        self.operation_combo.addItem("Common (Create Panels)")
        self.operation_combo.setToolTip("Cut removes the pillars. Common keeps the pillars.")
        form_layout.addRow("Operation:", self.operation_combo)

        # Strict Mode Toggle
        self.strict_check = QtWidgets.QCheckBox("Strict Full Hexagons Only")
        self.strict_check.setChecked(False)
        self.strict_check.setToolTip("Only generate hexagons that fit completely inside the object's boundaries.")
        form_layout.addRow("", self.strict_check)

        layout.addLayout(form_layout)
        layout.addStretch()

        # Connect Signals for Live Update
        self.radius_spin.valueChanged.connect(self.update_preview)
        self.gap_spin.valueChanged.connect(self.update_preview)
        self.offset_x_spin.valueChanged.connect(self.update_preview)
        self.offset_y_spin.valueChanged.connect(self.update_preview)
        self.operation_combo.currentIndexChanged.connect(self.update_preview)
        self.strict_check.toggled.connect(self.update_preview)

        # --- PREVIEW SETUP ---
        App.ActiveDocument.openTransaction("Hex Pattern Preview")

        self.preview_obj = App.ActiveDocument.addObject("Part::Feature", "HexPreview")
        self.target_obj.Visibility = False

        self.update_preview()

    def update_preview(self, *args):
        """Called automatically whenever any parameter is changed."""
        radius = self.radius_spin.value()
        gap = self.gap_spin.value()
        offset_x = self.offset_x_spin.value()
        offset_y = self.offset_y_spin.value()
        mode = "cut" if self.operation_combo.currentIndex() == 0 else "common"
        strict_mode = self.strict_check.isChecked()

        try:
            # Generate shape and assign to preview object
            new_shape = calculate_hex_shape(self.target_obj, radius, gap, mode, offset_x, offset_y, strict_mode)
            self.preview_obj.Shape = new_shape
            App.ActiveDocument.recompute()
        except Exception as e:
            App.Console.PrintError(f"Preview calculation error: {e}\n")

    def getStandardButtons(self):
        # In PySide6, use .value to get the integer representation of the enum flag
        return (QtWidgets.QDialogButtonBox.Ok | QtWidgets.QDialogButtonBox.Cancel).value

    def accept(self):
        mode = "cut" if self.operation_combo.currentIndex() == 0 else "common"
        op_text = "Lattice" if mode == "cut" else "Panels"
        self.preview_obj.Label = f"{self.target_obj.Name}_Hex{op_text}"

        App.ActiveDocument.commitTransaction()
        Gui.Control.closeDialog()

    def reject(self):
        App.ActiveDocument.abortTransaction()
        Gui.Control.closeDialog()


# 1. Check if a task panel is already active to prevent errors
if Gui.Control.activeDialog():
    Gui.Control.closeDialog()

# 2. Extract selection BEFORE launching the UI
sel = Gui.Selection.getSelection()
if not sel or not hasattr(sel[0], "Shape"):
    App.Console.PrintError("Error: Select a valid solid object first.\n")
else:
    # 3. Launch natively in the Tasks tab
    panel = SmartHexTaskPanel(sel[0])
    Gui.Control.showDialog(panel)
