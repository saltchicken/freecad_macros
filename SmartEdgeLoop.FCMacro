import FreeCAD as App
import FreeCADGui as Gui
import Part
import math
import os
from PySide6 import QtWidgets

from SharedLib.UI import BaseTaskPanel

# ==========================================
# CORE LOGIC: SMART EDGE LOOP
# ==========================================

def get_vertex_key(vertex, tolerance=4):
    """Rounds vertex coordinates to create a reliable dictionary key."""
    return (round(vertex.Point.x, tolerance),
            round(vertex.Point.y, tolerance),
            round(vertex.Point.z, tolerance))

def get_outward_tangent(edge, vertex_point):
    """Calculates the tangent vector of an edge pointing *away* from the vertex."""
    try:
        v_start = edge.Vertexes[0].Point
        v_end = edge.Vertexes[-1].Point

        if (v_start - vertex_point).Length < 1e-4:
            param = edge.ParameterRange[0]
            return edge.tangentAt(param).normalize()

        elif (v_end - vertex_point).Length < 1e-4:
            param = edge.ParameterRange[1]
            return edge.tangentAt(param).normalize().multiply(-1.0)

    except Exception:
        return None
    return None

def find_best_continuation(current_edge, current_edge_name, vertex_point, connected_edges, angle_tolerance):
    """Finds the smoothest connecting edge at a junction within the tolerance."""
    if not connected_edges:
        return None

    current_tangent = get_outward_tangent(current_edge, vertex_point)
    if not current_tangent:
        return connected_edges[0] if len(connected_edges) == 1 else None

    best_edge = None
    best_edge_name = None
    min_angle = 180.0

    for edge_name, edge in connected_edges:
        if edge_name == current_edge_name:
            continue

        next_tangent = get_outward_tangent(edge, vertex_point)
        if not next_tangent:
            continue

        dot_prod = current_tangent.dot(next_tangent)
        dot_prod = max(-1.0, min(1.0, dot_prod)) # Clamp for floating point errors

        angle = math.degrees(math.acos(dot_prod))
        deviation = abs(180.0 - angle)

        if deviation < min_angle and deviation <= angle_tolerance:
            min_angle = deviation
            best_edge = edge
            best_edge_name = edge_name

    return (best_edge_name, best_edge) if best_edge else None

def select_smart_loop(angle_tolerance=45.0):
    sel_ex = Gui.Selection.getSelectionEx()
    if not sel_ex:
        App.Console.PrintError("SmartLoop: Select an edge first.\n")
        return

    sel_object = sel_ex[0]
    obj = sel_object.Object
    sub_names = sel_object.SubElementNames

    if not sub_names:
        App.Console.PrintError("SmartLoop: Selection is empty.\n")
        return

    start_edge_name = None
    target_face_name = None

    for name in sub_names:
        if name.startswith("Edge") and not start_edge_name:
            start_edge_name = name
        elif name.startswith("Face") and not target_face_name:
            target_face_name = name

    if not start_edge_name:
        App.Console.PrintError("SmartLoop: You must select at least one Edge as a seed.\n")
        return

    shape = obj.Shape
    allowed_edge_names = None
    if target_face_name:
        allowed_edge_names = set()
        target_face = shape.getElement(target_face_name)
        
        for face_edge in target_face.Edges:
            for i, body_edge in enumerate(shape.Edges):
                if face_edge.isSame(body_edge):
                    allowed_edge_names.add(f"Edge{i+1}")
                    break

        if start_edge_name not in allowed_edge_names:
            App.Console.PrintError("SmartLoop: The selected seed Edge does not belong to the selected Face.\n")
            return

    vertex_map = {}
    for i, edge in enumerate(shape.Edges):
        edge_name = f"Edge{i+1}"
        for vertex in edge.Vertexes:
            v_key = get_vertex_key(vertex)
            if v_key not in vertex_map:
                vertex_map[v_key] = []
            vertex_map[v_key].append((edge_name, edge))

    start_edge = None
    for name, edge in vertex_map.get(get_vertex_key(shape.getElement(start_edge_name).Vertexes[0]), []):
        if name == start_edge_name:
            start_edge = edge
            break

    if not start_edge:
        return

    loop_edge_names = set([start_edge_name])
    endpoints = [start_edge.Vertexes[0], start_edge.Vertexes[-1]]

    for start_vertex in endpoints:
        current_vertex = start_vertex
        current_edge_name = start_edge_name
        current_edge = start_edge

        while True:
            v_key = get_vertex_key(current_vertex)
            connected = vertex_map.get(v_key, [])

            candidates = [e for e in connected if e[0] not in loop_edge_names]
            if allowed_edge_names:
                candidates = [e for e in candidates if e[0] in allowed_edge_names]

            if not candidates:
                break

            best_match = find_best_continuation(current_edge, current_edge_name, current_vertex.Point, candidates, angle_tolerance)
            if not best_match:
                break

            next_edge_name, next_edge = best_match
            loop_edge_names.add(next_edge_name)

            v0_key = get_vertex_key(next_edge.Vertexes[0])
            current_vertex = next_edge.Vertexes[1] if v0_key == v_key and len(next_edge.Vertexes) > 1 else next_edge.Vertexes[0]
            current_edge = next_edge
            current_edge_name = next_edge_name

    Gui.Selection.clearSelection()
    for edge_name in loop_edge_names:
        Gui.Selection.addSelection(obj, edge_name)

    mode_text = f" constrained to {target_face_name}" if target_face_name else ""
    App.Console.PrintMessage(f"SmartLoop: Selected {len(loop_edge_names)} edges at <= {angle_tolerance}° tolerance{mode_text}.\n")

# ==========================================
# CORE LOGIC: BULK EDGE CLASSIFICATION
# ==========================================

def map_and_classify_edges(obj):
    """Categorizes all edges of a solid into boundary, planar, convex, or concave."""
    shape = obj.Shape
    categories = {"boundary": [], "planar": [], "convex": [], "concave": []}
    
    edge_map = {}
    for i, edge in enumerate(shape.Edges):
        edge_name = f"Edge{i+1}"
        edge_map[edge_name] = {'edge': edge, 'faces': []}
        
    for face in shape.Faces:
        for face_edge in face.Edges:
            for e_name, data in edge_map.items():
                if data['edge'].isSame(face_edge):
                    data['faces'].append(face)
                    break
                    
    for edge_name, data in edge_map.items():
        edge = data['edge']
        faces = data['faces']
        
        if len(faces) == 1:
            categories["boundary"].append(edge_name)
        elif len(faces) >= 2:
            f1, f2 = faces[0], faces[1]
            
            P = edge.CenterOfMass
            C1 = f1.CenterOfMass
            C2 = f2.CenterOfMass
            
            v1 = (C1 - P)
            v2 = (C2 - P)
            
            if v1.Length > 0: v1.normalize()
            if v2.Length > 0: v2.normalize()
            
            v_avg = v1 + v2
            
            if v_avg.Length < 1e-4:
                categories["planar"].append(edge_name)
                continue
                
            v_avg.normalize()
            step_size = max(edge.Length * 0.01, 0.001)
            P_test = P + v_avg * step_size
            
            if shape.isInside(P_test, 1e-5, True):
                categories["convex"].append(edge_name)
            else:
                categories["concave"].append(edge_name)
                
    return categories

def select_edges_by_type(category_keys):
    """Clears selection and selects all edges matching the requested categories."""
    sel_ex = Gui.Selection.getSelectionEx()
    if not sel_ex:
        App.Console.PrintError("BulkSelect: Select a 3D object (or any of its faces/edges) first.\n")
        return
        
    obj = sel_ex[0].Object
    categories = map_and_classify_edges(obj)
    
    Gui.Selection.clearSelection()
    
    count = 0
    for key in category_keys:
        for edge_name in categories[key]:
            Gui.Selection.addSelection(obj, edge_name)
            count += 1
            
    App.Console.PrintMessage(f"BulkSelect: Selected {count} '{'+'.join(category_keys)}' edges.\n")

# ==========================================
# CORE LOGIC: DIRECTIONAL MATCHING
# ==========================================

def get_edge_direction(edge):
    """Returns the normalized vector spanning from the start to the end vertex of an edge."""
    if not edge.Vertexes or len(edge.Vertexes) < 2:
        return None
    
    v_start = edge.Vertexes[0].Point
    v_end = edge.Vertexes[-1].Point
    vec = v_end - v_start
    
    # If length is ~0, it's a closed loop (like a circle) and doesn't have a single direction
    if vec.Length > 1e-5:
        return vec.normalize()
    return None

def select_by_direction(mode="perpendicular", tolerance_deg=1.0):
    """Selects edges parallel or perpendicular to the currently selected edge."""
    sel_ex = Gui.Selection.getSelectionEx()
    if not sel_ex:
        App.Console.PrintError("DirectionSelect: Select a reference edge first.\n")
        return
        
    sel_object = sel_ex[0]
    obj = sel_object.Object
    sub_names = sel_object.SubElementNames

    ref_edge_name = next((name for name in sub_names if name.startswith("Edge")), None)
    if not ref_edge_name:
        App.Console.PrintError("DirectionSelect: You must select at least one Edge as a reference.\n")
        return

    shape = obj.Shape
    ref_edge = shape.getElement(ref_edge_name)
    ref_dir = get_edge_direction(ref_edge)
    
    if not ref_dir:
        App.Console.PrintError("DirectionSelect: Could not determine the linear direction of the reference edge.\n")
        return

    Gui.Selection.clearSelection()
    Gui.Selection.addSelection(obj, ref_edge_name) # Retain the seed edge
    
    rad_tol = math.radians(tolerance_deg)
    count = 0
    
    for i, edge in enumerate(shape.Edges):
        edge_name = f"Edge{i+1}"
        if edge_name == ref_edge_name:
            continue
            
        edge_dir = get_edge_direction(edge)
        if not edge_dir:
            continue # Skip closed circles/loops
            
        dot_prod = abs(ref_dir.dot(edge_dir))
        
        if mode == "perpendicular":
            # Perpendicular vectors have a dot product near 0
            if dot_prod <= math.sin(rad_tol):
                Gui.Selection.addSelection(obj, edge_name)
                count += 1
                
        elif mode == "parallel":
            # Parallel vectors have an absolute dot product near 1
            if dot_prod >= math.cos(rad_tol):
                Gui.Selection.addSelection(obj, edge_name)
                count += 1
                
    App.Console.PrintMessage(f"DirectionSelect: Selected {count} {mode} edges (tolerance ±{tolerance_deg}°).\n")


# ==========================================
# TOOL IMPLEMENTATION (Refactored)
# ==========================================
class SmartEdgeToolsTaskPanel(BaseTaskPanel):
    def __init__(self):
        ui_path = os.path.join(os.path.dirname(os.path.abspath(__file__)), "ui", "smart_edge_panel.ui")
        # has_preview=False disables the dummy object and timer
        super().__init__(ui_path, has_preview=False)

    def setup_ui(self):
        # We bind the buttons directly to the core functions
        self.form.btn_select.clicked.connect(lambda: select_smart_loop(self.form.tolerance_spin.value()))
        self.form.btn_para.clicked.connect(lambda: select_by_direction("parallel", 1.0))
        self.form.btn_perp.clicked.connect(lambda: select_by_direction("perpendicular", 1.0))
        self.form.btn_in.clicked.connect(lambda: select_edges_by_type(["concave"]))
        self.form.btn_out.clicked.connect(lambda: select_edges_by_type(["convex"]))
        self.form.btn_bound.clicked.connect(lambda: select_edges_by_type(["boundary"]))

    def getStandardButtons(self):
        # This tool only needs a Close button, not OK/Cancel
        return QtWidgets.QDialogButtonBox.Close.value

    def accept(self):
        Gui.Control.closeDialog()

if Gui.Control.activeDialog():
    Gui.Control.closeDialog()

panel = SmartEdgeToolsTaskPanel()
Gui.Control.showDialog(panel)

if Gui.Selection.getSelectionEx():
    try:
        select_smart_loop(45.0)
    except:
        pass
