import FreeCAD as App
import FreeCADGui as Gui
import Part
import math
from PySide6 import QtWidgets, QtCore
from PySide6.QtCore import Qt
import importlib

from SharedLib import MacroShared
importlib.reload(MacroShared)

# ==========================================
# CORE LOGIC: L-SYSTEM & 3D TURTLE
# ==========================================

def parse_rules(rule_str):
    """Parses a string like 'X=F[+X]; F=FF' into a dictionary."""
    rules = {}
    for rule in rule_str.split(';'):
        if '=' in rule:
            key, val = rule.split('=', 1)
            rules[key.strip()] = val.strip()
    return rules

def expand_l_system(axiom, rules, generations):
    """Applies the replacement rules for a given number of generations."""
    current = axiom
    for _ in range(generations):
        next_str = []
        for char in current:
            next_str.append(rules.get(char, char))
        current = "".join(next_str)
    return current

@MacroShared.with_undo("Smart L-System")
def generate_l_system_geometry(axiom, rule_str, generations, length, angle_deg, tube_radius):
    doc = App.ActiveDocument
    if doc is None:
        App.Console.PrintError("Error: No active document.\n")
        return

    # 1. Expand the string
    rules = parse_rules(rule_str)
    l_string = expand_l_system(axiom, rules, generations)
    
    App.Console.PrintMessage(f"L-System expanded to {len(l_string)} instructions.\n")

    # 2. 3D Turtle setup
    # X=Right, Y=Up, Z=Forward (Drawing Direction)
    pos = App.Vector(0, 0, 0)
    rot = App.Rotation(0, 0, 0)  
    stack = []
    
    edges = []
    tubes = []

    # 3. Execute Turtle Instructions
    for char in l_string:
        if char == 'F':
            # Draw forward
            current_dir = rot.multVec(App.Vector(0, 0, 1))
            end_pos = pos + current_dir * length
            
            # Create Wireframe Edge
            edge = Part.LineSegment(pos, end_pos).toShape()
            edges.append(edge)
            
            # Create Tube Geometry if requested
            if tube_radius > 0:
                vec = end_pos - pos
                if vec.Length > 1e-5:
                    cyl = Part.makeCylinder(tube_radius, vec.Length)
                    z_vec = App.Vector(0, 0, 1)
                    
                    # Prevent gimbal lock if pointing straight down
                    if z_vec.dot(vec.normalize()) < -0.9999:
                        align_rot = App.Rotation(App.Vector(1, 0, 0), 180)
                    else:
                        align_rot = App.Rotation(z_vec, vec)
                    
                    cyl.Placement = App.Placement(pos, align_rot)
                    tubes.append(cyl)

            pos = end_pos
            
        elif char == 'f':
            # Move forward without drawing
            current_dir = rot.multVec(App.Vector(0, 0, 1))
            pos = pos + current_dir * length
            
        elif char == '+': # Yaw Right (around Y)
            rot = rot.multiply(App.Rotation(App.Vector(0, 1, 0), angle_deg))
        elif char == '-': # Yaw Left (around Y)
            rot = rot.multiply(App.Rotation(App.Vector(0, 1, 0), -angle_deg))
            
        elif char == '^': # Pitch Up (around X)
            rot = rot.multiply(App.Rotation(App.Vector(1, 0, 0), angle_deg))
        elif char == '&': # Pitch Down (around X)
            rot = rot.multiply(App.Rotation(App.Vector(1, 0, 0), -angle_deg))
            
        elif char == '\\': # Roll Right (around Z)
            rot = rot.multiply(App.Rotation(App.Vector(0, 0, 1), angle_deg))
        elif char == '/': # Roll Left (around Z)
            rot = rot.multiply(App.Rotation(App.Vector(0, 0, 1), -angle_deg))
            
        elif char == '[':
            # Push State
            stack.append((App.Vector(pos), App.Rotation(rot)))
        elif char == ']':
            # Pop State
            if stack:
                pos, rot = stack.pop()

    if not edges:
        App.Console.PrintWarning("No printable geometry generated by these rules.\n")
        return

    # 4. Compile Geometry into FreeCAD
    result_group = doc.addObject("App::DocumentObjectGroup", "L_System")
    
    # Wireframe output
    wire_comp = Part.makeCompound(edges)
    wire_obj = doc.addObject("Part::Feature", "Wireframe")
    wire_obj.Shape = wire_comp
    wire_obj.ViewObject.LineColor = (0.1, 0.8, 0.3)
    wire_obj.ViewObject.LineWidth = 2.0
    result_group.addObject(wire_obj)

    # Solid Tube output (if enabled)
    if tube_radius > 0:
        tube_comp = Part.makeCompound(tubes)
        solid_obj = doc.addObject("Part::Feature", "SolidBranches")
        solid_obj.Shape = tube_comp
        solid_obj.ViewObject.ShapeColor = (0.4, 0.2, 0.1)
        result_group.addObject(solid_obj)
        wire_obj.ViewObject.Visibility = False # Hide wires if solid exists

    doc.recompute()
    App.Console.PrintMessage("Smart L-System generation complete!\n")


# ==========================================
# GUI LOGIC (Native Task Panel)
# ==========================================
class SmartLSystemTaskPanel:
    def __init__(self):
        self.form = QtWidgets.QWidget()
        layout = QtWidgets.QVBoxLayout(self.form)

        instruction_text = (
            "<b>Organic Generator</b><br>"
            "Generates fractal geometry based on string rules."
        )
        layout.addWidget(QtWidgets.QLabel(instruction_text))

        form_layout = QtWidgets.QFormLayout()

        # Presets
        self.preset_cb = QtWidgets.QComboBox()
        self.presets = {
            "3D Fractal Tree": {"axiom": "X", "rules": "X=F[+X][^X][-X][&X]; F=FF", "angle": 25.0, "gen": 4},
            "2D Fern": {"axiom": "X", "rules": "X=F+[[X]-X]-F[-FX]+X; F=FF", "angle": 25.0, "gen": 5},
            "Dragon Curve": {"axiom": "FX", "rules": "X=X+YF+; Y=-FX-Y", "angle": 90.0, "gen": 9},
            "Koch Snowflake": {"axiom": "F++F++F", "rules": "F=F-F++F-F", "angle": 60.0, "gen": 3},
            "Sierpinski Triangle": {"axiom": "F-G-G", "rules": "F=F-G+F+G-F; G=GG", "angle": 120.0, "gen": 5}
        }
        self.preset_cb.addItems(self.presets.keys())
        self.preset_cb.currentIndexChanged.connect(self.load_preset)
        form_layout.addRow("Preset:", self.preset_cb)

        # Axiom
        self.axiom_input = QtWidgets.QLineEdit()
        form_layout.addRow("Axiom (Start):", self.axiom_input)

        # Rules
        self.rules_input = QtWidgets.QLineEdit()
        self.rules_input.setToolTip("Format: 'A=F[+A]; F=FF'. Separate rules with semicolons.")
        form_layout.addRow("Rules:", self.rules_input)

        # Generations
        self.gen_spin = QtWidgets.QSpinBox()
        self.gen_spin.setRange(1, 12)
        form_layout.addRow("Generations:", self.gen_spin)

        # Angle
        self.angle_spin = QtWidgets.QDoubleSpinBox()
        self.angle_spin.setRange(0.0, 360.0)
        self.angle_spin.setSuffix(" °")
        form_layout.addRow("Branch Angle:", self.angle_spin)

        # Length
        self.length_spin = QtWidgets.QDoubleSpinBox()
        self.length_spin.setRange(0.1, 100.0)
        self.length_spin.setValue(5.0)
        self.length_spin.setSuffix(" mm")
        form_layout.addRow("Segment Length:", self.length_spin)

        # Tube Radius
        self.radius_spin = QtWidgets.QDoubleSpinBox()
        self.radius_spin.setRange(0.0, 50.0)
        self.radius_spin.setValue(0.5)
        self.radius_spin.setSingleStep(0.1)
        self.radius_spin.setSuffix(" mm")
        self.radius_spin.setToolTip("Set to 0 for Wireframe only. Values > 0 create solid tubes.")
        form_layout.addRow("Tube Radius:", self.radius_spin)

        layout.addLayout(form_layout)

        # Generate Button
        self.btn_gen = QtWidgets.QPushButton("Grow Geometry")
        self.btn_gen.setStyleSheet("font-weight: bold; padding: 10px; margin-top: 10px;")
        self.btn_gen.clicked.connect(self.execute_growth)
        layout.addWidget(self.btn_gen)

        layout.addStretch()

        # Load default preset
        self.load_preset()

    def load_preset(self):
        preset_name = self.preset_cb.currentText()
        data = self.presets[preset_name]
        self.axiom_input.setText(data["axiom"])
        self.rules_input.setText(data["rules"])
        self.angle_spin.setValue(data["angle"])
        self.gen_spin.setValue(data["gen"])

    def execute_growth(self):
        generate_l_system_geometry(
            self.axiom_input.text(),
            self.rules_input.text(),
            self.gen_spin.value(),
            self.length_spin.value(),
            self.angle_spin.value(),
            self.radius_spin.value()
        )

    def getStandardButtons(self):
        return QtWidgets.QDialogButtonBox.Close.value

    def reject(self):
        Gui.Control.closeDialog()


if Gui.Control.activeDialog():
    Gui.Control.closeDialog()

panel = SmartLSystemTaskPanel()
Gui.Control.showDialog(panel)
