import FreeCAD as App
import FreeCADGui as Gui
import Part
import math
from PySide6 import QtWidgets, QtCore
import importlib

from SharedLib import MacroShared
importlib.reload(MacroShared)

# ==========================================
# CORE LOGIC
# ==========================================

def parse_rules(rule_str):
    rules = {}
    for rule in rule_str.split(';'):
        if '=' in rule:
            key, val = rule.split('=', 1)
            rules[key.strip()] = val.strip()
    return rules

def expand_l_system(axiom, rules, generations):
    current = axiom
    for _ in range(generations):
        next_str = []
        for char in current:
            next_str.append(rules.get(char, char))
        current = "".join(next_str)
    return current

@MacroShared.with_undo("Smart Edge Growth")
def generate_bridging_geometry(axiom, rule_str, generations, angle_deg, base_radius):
    doc = App.ActiveDocument
    if not doc:
        App.Console.PrintError("Error: No active document.\n")
        return

    # 1. Selection Validation
    sel_ex = Gui.Selection.getSelectionEx()
    edges = []
    for sel_obj in sel_ex:
        for sub_obj in sel_obj.SubObjects:
            if hasattr(sub_obj, "ShapeType") and sub_obj.ShapeType == "Edge":
                edges.append(sub_obj)

    if len(edges) != 2:
        App.Console.PrintError(f"Error: Found {len(edges)} edge(s). Please Ctrl+Click exactly two parallel edges.\n")
        return

    edge1 = edges[0]
    edge2 = edges[1]

    # 2. Calculate the Sketch Plane Math
    p1 = edge1.CenterOfMass
    p2 = edge2.CenterOfMass

    e1_vec = edge1.Vertexes[-1].Point - edge1.Vertexes[0].Point
    e2_vec = edge2.Vertexes[-1].Point - edge2.Vertexes[0].Point

    if e1_vec.Length < 1e-4 or e2_vec.Length < 1e-4: return

    e1_dir = e1_vec.normalize()
    e2_dir = e2_vec.normalize()

    if abs(e1_dir.dot(e2_dir)) < 0.98:
        App.Console.PrintError("Error: The selected edges do not appear to be parallel.\n")
        return

    # X-axis along edge 1, Y-axis points toward edge 2
    x_dir = e1_dir
    bridge_vec = p2 - p1
    z_dir = x_dir.cross(bridge_vec).normalize()
    y_dir = z_dir.cross(x_dir).normalize()

    gap_distance = bridge_vec.dot(y_dir)

    if gap_distance < 1e-4:
        App.Console.PrintError("Error: Edges are overlapping or too close.\n")
        return

    # 3. L-System Expansion
    rules = parse_rules(rule_str)
    l_string = expand_l_system(axiom, rules, generations)

    # 4. 3D Turtle Generation (Growing along local Y-axis)
    pos = App.Vector(0, 0, 0)
    rot = App.Rotation(0, 0, 0)
    stack = []
    tubes = []
    length = 1.0

    z_vec = App.Vector(0, 0, 1)

    for char in l_string:
        if char == 'F' or char == 'f':
            current_dir = rot.multVec(App.Vector(0, 1, 0)) # Grow along Y axis
            end_pos = pos + current_dir * length

            if char == 'F':
                vec = end_pos - pos
                if vec.Length > 1e-5:
                    cyl = Part.makeCylinder(base_radius, vec.Length)
                    vec_dir = vec.normalize()
                    if z_vec.dot(vec_dir) < -0.9999:
                        align_rot = App.Rotation(App.Vector(1, 0, 0), 180)
                    else:
                        align_rot = App.Rotation(z_vec, vec_dir)
                    cyl.Placement = App.Placement(pos, align_rot)
                    tubes.append(cyl)
            pos = end_pos

        elif char == '+': rot = rot.multiply(App.Rotation(App.Vector(0, 0, 1), angle_deg))  # Yaw Right
        elif char == '-': rot = rot.multiply(App.Rotation(App.Vector(0, 0, 1), -angle_deg)) # Yaw Left
        elif char == '^': rot = rot.multiply(App.Rotation(App.Vector(1, 0, 0), angle_deg))  # Pitch Up
        elif char == '&': rot = rot.multiply(App.Rotation(App.Vector(1, 0, 0), -angle_deg)) # Pitch Down
        elif char == '\\': rot = rot.multiply(App.Rotation(App.Vector(0, 1, 0), angle_deg)) # Roll Right
        elif char == '/': rot = rot.multiply(App.Rotation(App.Vector(0, 1, 0), -angle_deg)) # Roll Left

        elif char == '[': stack.append((App.Vector(pos), App.Rotation(rot)))
        elif char == ']':
            if stack:
                pos, rot = stack.pop()

    if not tubes:
        App.Console.PrintWarning("Warning: No geometry generated by these rules.\n")
        return

    solid_compound = Part.makeCompound(tubes)

    # 5. Scale to perfectly bridge the gap
    bbox = solid_compound.BoundBox
    max_y = bbox.YMax - bbox.YMin
    scale_factor = gap_distance / max_y if max_y > 1e-5 else 1.0

    scale_mat = App.Matrix()
    scale_mat.scale(scale_factor, scale_factor, scale_factor)
    solid_compound.transformShape(scale_mat)

    # 6. Align and Place Geometry in 3D Space
    mat = App.Matrix(
        x_dir.x, y_dir.x, z_dir.x, p1.x,
        x_dir.y, y_dir.y, z_dir.y, p1.y,
        x_dir.z, y_dir.z, z_dir.z, p1.z,
        0.0,     0.0,     0.0,     1.0
    )
    solid_compound.Placement = App.Placement(mat)

    # 7. Render in FreeCAD
    growth_obj = doc.addObject("Part::Feature", "Bridging_Growth")
    growth_obj.Shape = solid_compound
    growth_obj.ViewObject.ShapeColor = (0.2, 0.6, 0.3)

    doc.recompute()
    App.Console.PrintMessage(f"Generated growth bridging a {gap_distance:.2f}mm gap!\n")


# ==========================================
# GUI LOGIC (Native Task Panel)
# ==========================================

class SmartGrowthTaskPanel:
    def __init__(self):
        self.form = QtWidgets.QWidget()
        layout = QtWidgets.QVBoxLayout(self.form)

        instruction_text = (
            "<b>1.</b> Ctrl+Click exactly 2 parallel edges.<br>"
            "<b>2.</b> Select an algorithm or type rules.<br>"
            "<b>3.</b> Click Generate to bridge the gap."
        )
        layout.addWidget(QtWidgets.QLabel(instruction_text))

        form_layout = QtWidgets.QFormLayout()

        # Presets
        self.preset_cb = QtWidgets.QComboBox()
        self.presets = {
            "Mycelium Web": {"axiom": "[--X][X][++X]", "rules": "X=F[+X][-X]F[\\X][/X]X; F=FF", "angle": 30.0, "gen": 5},
            "2D Fern": {"axiom": "X", "rules": "X=F+[[X]-X]-F[-FX]+X; F=FF", "angle": 25.0, "gen": 5},
            "3D Fern (Spiral)": {"axiom": "X", "rules": "X=F+\\[[X]-X]-F[-FX]+X; F=FF", "angle": 25.0, "gen": 5},
            "3D Fractal Tree": {"axiom": "X", "rules": "X=F[+X][^X][-X][&X]; F=FF", "angle": 25.0, "gen": 4},
            "Dragon Curve": {"axiom": "FX", "rules": "X=X+YF+; Y=-FX-Y", "angle": 90.0, "gen": 8},
            "Sierpinski Arrow": {"axiom": "YF", "rules": "X=YF+XF+Y; Y=XF-YF-X", "angle": 60.0, "gen": 5},
            "Koch Snowflake": {"axiom": "F++F++F", "rules": "F=F-F++F-F", "angle": 60.0, "gen": 3}
        }
        self.preset_cb.addItems(self.presets.keys())
        self.preset_cb.currentIndexChanged.connect(self.load_preset)
        form_layout.addRow("Algorithm:", self.preset_cb)

        # Axiom
        self.axiom_input = QtWidgets.QLineEdit()
        form_layout.addRow("Start (Axiom):", self.axiom_input)

        # Rules
        self.rules_input = QtWidgets.QLineEdit()
        form_layout.addRow("Rules:", self.rules_input)

        # Generations
        self.gen_spin = QtWidgets.QSpinBox()
        self.gen_spin.setRange(1, 10)
        form_layout.addRow("Complexity (Gen):", self.gen_spin)

        # Angle
        self.angle_spin = QtWidgets.QDoubleSpinBox()
        self.angle_spin.setRange(0.0, 360.0)
        self.angle_spin.setSuffix(" °")
        form_layout.addRow("Branch Angle:", self.angle_spin)

        # Tube Radius
        self.radius_spin = QtWidgets.QDoubleSpinBox()
        self.radius_spin.setRange(0.01, 1.0)
        self.radius_spin.setSingleStep(0.01)
        self.radius_spin.setValue(0.08)
        self.radius_spin.setToolTip("Thickness relative to branch length. Larger = chunkier.")
        form_layout.addRow("Tube Thickness:", self.radius_spin)

        layout.addLayout(form_layout)

        # Generate Button
        self.btn_gen = QtWidgets.QPushButton("Bridge Edges")
        self.btn_gen.setStyleSheet("font-weight: bold; padding: 10px; margin-top: 10px;")
        self.btn_gen.clicked.connect(self.execute_growth)
        layout.addWidget(self.btn_gen)

        layout.addStretch()
        self.load_preset()

    def load_preset(self):
        preset_name = self.preset_cb.currentText()
        data = self.presets[preset_name]
        self.axiom_input.setText(data["axiom"])
        self.rules_input.setText(data["rules"])
        self.angle_spin.setValue(data["angle"])
        self.gen_spin.setValue(data["gen"])

    def execute_growth(self):
        generate_bridging_geometry(
            self.axiom_input.text(),
            self.rules_input.text(),
            self.gen_spin.value(),
            self.angle_spin.value(),
            self.radius_spin.value()
        )
        # We do NOT close the dialog here, so you can rapidly test different
        # algorithms, angles, and thicknesses without re-opening the macro.

    def getStandardButtons(self):
        return QtWidgets.QDialogButtonBox.Close.value

    def reject(self):
        Gui.Control.closeDialog()


if Gui.Control.activeDialog():
    Gui.Control.closeDialog()

panel = SmartGrowthTaskPanel()
Gui.Control.showDialog(panel)
